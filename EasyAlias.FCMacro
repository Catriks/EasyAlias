# -*- coding: utf-8 -*-
import FreeCAD
import re
from PySide import QtGui

"""
EasyAlias.FCMacro.py

This macro can be used to easily create aliases based on the contents of selected spreadsheet
cells in the previous column. As an example, suppose you wish to have the following:

A1: content = 'radius', B1: content = '5', alias = 'radius'
A2: content = 'height', B1: content = '15', alias = 'height'

The traditional way to set this up would be:
Select A1
Enter radius
Select B1
Enter 5
Right-click B1
Select properties
Select Alias
Enter radius
click OK
Select A2
Enter height
Select B2
Enter 15
Right-click B2
Select Properties
Select Alias
Enter height
Click OK

Using this macro, the work flow becomes:
Select A1
Enter radius
Select B1
Enter 5
Select A2
Enter height
Select B2
Enter 15
Select A1 through A2
Run the EasyAlias macro
Done

"""

__title__ = "EasyAlias"
__author__ = "TheMarkster and rosta"
__url__ = "https://wiki.freecadweb.org/Macro_EasyAlias"
__Wiki__ = "https://wiki.freecadweb.org/Macro_EasyAlias"
__date__ = "2024.12.24" #year.month.date
__version__ = __date__
__icon__ = "https://www.freecadweb.org/wiki/images/5/5e/Easy-alias-icon.png"

CELL_ADDR_RE = re.compile(r"([A-Za-z]+)([1-9]\d*)")
CUSTOM_ALIAS_RE = re.compile(r".*\((.*)\)")
MAGIC_NUMBER = 64
REPLACEMENTS = {
    " ": "_",
    ".": "_",
    "ä": "ae",
    "ö": "oe",
    "ü": "ue",
    "Ä": "Ae",
    "Ö": "Oe",
    "Ü": "Ue",
    "ß": "ss",
    "'": ""
}

def getSpreadsheets():
    """
    Returns a set of selected spreadsheets in the active document or None if none is selected.
    :returns: a set of selected spreadsheets in the active document or None if none is selected
    :rtype: set
    """

    spreadsheets = set()
    for selectedObject in Gui.Selection.getSelection():
        if selectedObject.TypeId == 'Spreadsheet::Sheet':
            spreadsheets.add(selectedObject)
        elif selectedObject.TypeId == "App::Link":
            linkedObject = selectedObject.LinkedObject
            if linkedObject.TypeId == 'Spreadsheet::Sheet':
                spreadsheets.add(linkedObject)
    if spreadsheets:
        return spreadsheets
    else:
        # check if there is only one spreadsheet and use that one if none are selected
        doc = FreeCAD.ActiveDocument
        if not doc:
            return spreadsheets
        all_spreadsheets = [obj for obj in doc.Objects if obj.isDerivedFrom("Spreadsheet::Sheet")]
        if len(all_spreadsheets) == 1:
            return set(all_spreadsheets)
    return spreadsheets

# The original implementatin of a1_to_rowcol and rowcol_to_a1 can be found here:
# https://github.com/burnash/gspread/blob/master/gspread/utils.py

def a1_to_rowcol(label:str):
    """Translates a cell's address in A1 notation to a tuple of integers.
    :param str label: A cell label in A1 notation, e.g. 'B1'. Letter case is ignored.
    :returns: a tuple containing `row` and `column` numbers. Both indexed from 1 (one).
    :rtype: tuple
    Example:
    >>> a1_to_rowcol('A1')
    (1, 1)
    """

    match = CELL_ADDR_RE.match(label)

    row = int(match.group(2))

    column_label = match.group(1).upper()
    column = 0
    for i, c in enumerate(reversed(column_label)):
        column += (ord(c) - MAGIC_NUMBER) * (26**i)

    return (row, column)

def rowcol_to_a1(row:int, column:int):
    """Translates a row and column cell address to A1 notation.
    :param row: The row of the cell to be converted. Rows start at index 1.
    :type row: int, str
    :param col: The column of the cell to be converted. Columns start at index 1.
    :type row: int, str
    :returns: a string containing the cell's coordinates in A1 notation.
    Example:
    >>> rowcol_to_a1(1, 1)
    A1
    """

    row = int(row)

    column = int(column)
    dividend = column
    column_label = ""
    while dividend:
        (dividend, mod) = divmod(dividend, 26)
        if mod == 0:
            mod = 26
            dividend -= 1
        column_label = chr(mod + MAGIC_NUMBER) + column_label

    label = "{}{}".format(column_label, row)

    return label

def textToAlias(text:str):
    # support for custom aliases between parentheses
    match = CUSTOM_ALIAS_RE.match(text)
    if match:
        return match.group(1)

    for character in REPLACEMENTS:
        text = text.replace(character,REPLACEMENTS.get(character))
    return text

def main():
    spreadsheets = getSpreadsheets()
    if not spreadsheets:
        QtGui.QMessageBox.critical(None, "Error",
            "No spreadsheet selected.\nPlease select a spreadsheet in the tree view.")
        return
    for spreadsheet in spreadsheets:
        selected_cells = spreadsheet.ViewObject.getView().selectedCells()
        if not selected_cells:
            QtGui.QMessageBox.critical(None, "Error",
                "No cells selected.\nPlease select at least one cell.")
            return

        # Parse all selected cells into (row, col) and find min row and min col
        cell_indices = [a1_to_rowcol(cell) + (cell,) for cell in selected_cells]
        if not cell_indices:
            QtGui.QMessageBox.critical(None, "Error",
                "No valid cells selected.")
            return

        min_row = min(row for row, col, cell in cell_indices)
        min_col = min(col for row, col, cell in cell_indices)

        # Header cells: all selected cells in the header row (min_row)
        header_cells = [(cell, col) for row, col, cell in cell_indices if row == min_row]
        # Value cells: all selected cells in the leftmost selected column (min_col), but not in header row
        value_cells = [(cell, row) for row, col, cell in cell_indices if col == min_col and row != min_row]

        if header_cells and value_cells:
            # Table mode: assign {A value}_{header} to each cell in the row
            headers = {}
            for cell, col in header_cells:
                header_text = spreadsheet.getContents(cell)
                headers[col] = textToAlias(header_text)
            for value_cell, value_row in value_cells:
                value = spreadsheet.getContents(value_cell)
                value_alias = textToAlias(value)
                for col in headers:
                    if col == min_col:
                        continue  # skip the value column itself
                    target_cell = rowcol_to_a1(value_row, col)
                    alias = f"{value_alias}_{headers[col]}"
                    try:
                        spreadsheet.setAlias(target_cell, alias)
                    except Exception as e:
                        QtGui.QMessageBox.critical(None, "Error",
                            f"Unable to set alias <i>{alias}</i> at cell {target_cell} "
                            f"<br>in spreadsheet <i>{spreadsheet.FullName}</i>.<br><br>"
                            "<b>Remember, aliases cannot begin with a numeral or an underscore or contain any invalid characters.</b>")
        elif value_cells:
            # Original mode: assign alias from value cell to cell to its right
            for value_cell, value_row in value_cells:
                value = spreadsheet.getContents(value_cell)
                value_alias = textToAlias(value)
                target_cell = rowcol_to_a1(value_row, min_col + 1)
                try:
                    spreadsheet.setAlias(target_cell, value_alias)
                except Exception as e:
                    QtGui.QMessageBox.critical(None, "Error",
                        f"Unable to set alias <i>{value_alias}</i> at cell {target_cell} "
                        f"<br>in spreadsheet <i>{spreadsheet.FullName}</i>.<br><br>"
                        "<b>Remember, aliases cannot begin with a numeral or an underscore or contain any invalid characters.</b>")
        else:
            QtGui.QMessageBox.critical(None, "Error",
                "Please select at least one cell in the leftmost column, or the header row and value cells.")
            return

    App.ActiveDocument.recompute()

main()
